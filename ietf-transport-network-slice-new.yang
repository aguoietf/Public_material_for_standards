module ietf-transport-network-slice {
     yang-version 1.1;
     namespace
       "urn:ietf:params:xml:ns:yang:ietf-transport-network-slice";
     prefix "tns";

     import ietf-inet-types {
       prefix inet;
       reference 
         "RFC 6991: Common YANG Data Types";
     }

     import ietf-te-types {
       prefix "te-types";
       reference
         "RFC 8776: Traffic Engineering Common YANG Types";
     }

     import ietf-network-slice-service {
       prefix "ietf-nss";
       reference
         "draft-ietf-teas-ietf-network-slice-nbi-yang-00: IETF Network Slice Service YANG Model";
     }
	 
     organization
       "IETF CCAMP Working Group";
     contact
       "WG Web: <http://tools.ietf.org/wg/ccamp/>
        WG List: <mailto:ccamp@ietf.org>

        Editor: Haomian Zheng
                <mailto:zhenghaomian@huawei.com>

        Editor: Italo Busi
                <mailto:italo.busi@huawei.com>

        Editor: Aihua Guo
                <mailto:aihuaguo.ietf@gmail.com>

        Editor: Sergio Belotti
                <mailto:sergio.belotti@nokia.com>";

     description
       "This module defines a base YANG data model for configuring
        generic network slices in optical transport networks, e.g.,
        Optical Transport Network (OTN).

        The model fully conforms to the Network Management Datastore
        Architecture (NMDA).

        Copyright (c) 2022 IETF Trust and the persons
        identified as authors of the code.  All rights reserved.

        Redistribution and use in source and binary forms, with or
        without modification, is permitted pursuant to, and subject
        to the license terms contained in, the Simplified BSD
        License set forth in Section 4.c of the IETF Trust's Legal
        Provisions Relating to IETF Documents
        (https://trustee.ietf.org/license-info).
        This version of this YANG module is part of RFC XXXX; see
        the RFC itself for full legal notices.";

     revision "2022-03-04" {
       description
         "Latest revision of NBI YANG model for OTN slicing.";
       reference
         "draft-ietf-ccamp-yang-otn-slicing-01: Framework and Data
          Model for OTN Network Slicing";
     }

     //network topology grouping
     grouping network-topology-def {
       description
         "Network topology definition";
       list node {
         key "node-id";
         description
         "The inventory of nodes of this topology.";
         leaf node-id {
           type inet:uri;
           description
             "Node identifier.";
         }
         uses node-slo;
         list termination-point {
           key "tp-id";
           description
             "TP identifier";
           leaf tp-id {
             type inet:uri;
             description
               "Termination point identifier.";
           }
           leaf sdp-id {
             type leafref {
               path "/ietf-nss:network-slice-services/ietf-nss:slice-service[service-id=current()"+
                  "/../../../../../service-id]/ietf-nss:sdps"+"/ietf-nss:sdp/ietf-nss:sdp-id";
             }
             description
               "Relative reference to SDP id.";
           }
         }
       }
       list link {
         key "link-id";
         description
           "Link identifier.";
         leaf link-id {
           type inet:uri;
           description
             "Link identifier.";
         }
         uses link-slo;
         container source {
           description
             "Link source node";
           leaf source-node {
             type leafref {
               path "../../../node/node-id";
             }
             description
               "Source node identifier, must be in same topology.";
           }
           leaf source-tp {
             type leafref {
               path "../../../node[node-id=current()/../"+
                    "source-node]/termination-point/tp-id";
             }
             description
               "Termination point within source node that terminates
                the link.";
           }
         }
         container destination {
           description
             "Link destination node";
           leaf dest-node {
             type leafref {
               path "../../../node/node-id";
             }
             description
               "Destination node identifier, must be in same
                topology.";
           }
           leaf dest-tp {
             type leafref {
               path "../../../node[node-id=current()/../"+
                    "dest-node]/termination-point/tp-id";
             }
             description
               "Termination point within destination node that
                terminates the link.";
           }
         }
       }
     }

     grouping node-slo {
       description
         "Node SLO";
       container slo {
         description
           "SLO configuration of a node";
         leaf isolation-level {
           type identityref {
             base isolation-level;
           }
           description
             "A network slice instance may be fully or partly,
              logically and/or physically, isolated from another
              network slice instance. This attribute describes
              different types of isolation:";
         }
       }
     }

     grouping link-slo {
       description
         "Link SLO";
       container slo {
         description
           "SLO configuration of a link";
         leaf delay-tolerance {
           type boolean;
           description
             "'true' if is not too critical how long it takes to
              deliver the amount of data.";
           reference
             "GSMA-NS-Template: Generic Network Slice Template,
              Version 3.0.";
         }
         leaf-list periodicity {
           type uint64;
           units seconds;
           description
             "A list of periodicities supported by the network
              slice.";
           reference
             "GSMA-NS-Template: Generic Network Slice Template,
              Version 3.0.";
         }
         leaf isolation-level {
           type identityref {
             base isolation-level;
           }
           description
             "A network slice instance may be fully or partly,
              logically and/or physically, isolated from another
              network slice instance. This attribute describes
              different types of isolation:";
         }
       }
     }

     grouping topology-ref {
       leaf topology-id {
         type leafref {
           path "../../../network-topologies/network-topology"+
                "/topology-id";
         }
         description
           "Relative reference to network topology id.";
       }
       uses explicit-path;
     }

     grouping explicit-path {
       description
         "Explicit path for a connectivity matrix entry";

       list explicit-path {
         key "tp-id";
         description
           "List of TPs within a network topology that form a
            path.";
         leaf tp-id {
           type leafref {
             path "/ietf-nss:network-slice-services/ietf-nss:slice-service[service-id=current()"+
                  "/../../service-id]/network-topologies"+
                  "/network-topology[topology-id=current()"+
                  "/../../topology-id]/node/termination-point"+
                  "/tp-id";
           }
           description
             "Relative reference to TP id.";
         }
       }
     }

     /*
      * Augmented data nodes
      */
	 augment "ietf-nss:network-slice-services" +
             "/ietf-nss:slice-service" {
	   container network-topologies {
	     description
		   "Set of network topologies referenced by network slices";

	     list network-topology {
		   key "topology-id";
		   description
		     "List of network topologies";
		   leaf topology-id {
		     type string;
		     description
			   "Topology identifier";
		   }
		   uses network-topology-def;
	     }
	   }
     }
	 
	 augment "ietf-nss:network-slice-services" +
             "/ietf-nss:connection-groups" +
             "/ietf-nss:connectivity-construct"{
       description "Add toplogy id and explicit path to a connectivity construct"
	   uses topology-ref;
     }
   }
