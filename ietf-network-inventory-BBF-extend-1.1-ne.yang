module ietf-network-inventory {
  yang-version 1.1;
  namespace "urn:ietf:params:xml:ns:yang:ietf-network-inventory";
  prefix ni;
  
  import iana-hardware {
    prefix ianahw;
    reference
    "https://www.iana.org/assignments/yang-parameters";
  }

  import ietf-yang-types {
    prefix yang;
    reference
      "RFC6991: Common YANG Data Types.";
  }
  
  import ietf-inet-types {
    prefix inet;
    reference
      "RFC6991: Common YANG Data Types.";
  } 

  organization
    "IETF IVY Working Group";
  contact
    "WG Web:   <https://datatracker.ietf.org/wg/ivy/>
     WG List:  <mailto:inventory-yang@ietf.org>

     Editor:   Chaode Yu
               <yuchaode@huawei.com>

     Editor:   Sergio Belotti
               <sergio.belotti@nokia.com>

     Editor:   Jean-Francois Bouquier
               <jeff.bouquier@vodafone.com>

     Editor:   Fabio Peruzzini
               <fabio.peruzzini@telecomitalia.it>

     Editor:   Phil Bedard
               <phbedard@cisco.com>";

  description
    "This module defines a base model for retrieving network 
    inventory.

    The model fully conforms to the Network Management 
    Datastore Architecture (NMDA).
    
    Copyright (c) 2023 IETF Trust and the persons
    identified as authors of the code.  All rights reserved.

    Redistribution and use in source and binary forms, with or
    without modification, is permitted pursuant to, and subject
    to the license terms contained in, the Revised BSD License
    set forth in Section 4.c of the IETF Trust's Legal Provisions
    Relating to IETF Documents
    (https://trustee.ietf.org/license-info).

    This version of this YANG module is part of RFC XXXX; see
    the RFC itself for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.";

  // RFC Ed.: replace XXXX with actual RFC number and remove this
  // note.
  // RFC Ed.: update the date below with the date of RFC publication
  // and remove this note.
  
  revision 2024-03-04 {
    description
      "Initial version";
    reference
      "RFC XXXX: A YANG Data Model for Network Inventory.";
      //RFC Editor: replace XXXX with actual RFC number, update date
      //information and remove this note
  }

  identity non-hardware-component-class {
    description
      "Base identity for non hardware components (e.g., software 
      components) in a managed device.";
  }

  identity ne-type {
    description
      "Base identity for network element (NE) types.";
  }

    identity ne-physical {
      base ni:ne-type;
      description
        "A physical network element (NE). ";
    }

  grouping common-entity-attributes {
    description
      "A set of attributes which are common to all the entities
      (e.g., component, equipment room) defined in this module.";
    leaf uuid {
      config false;
      type yang:uuid;
      description
        "Uniquely identifies an entity (e.g., component).";
    }
    leaf name {
      type string;
      description
        "A name for an entity (e.g., component), as specified by
        a network manager, that provides a non-volatile 'handle'
        for the entity and that can be modified anytime during the
        entity lifetime.

        If no configured value exists, the server MAY set the value
        of this node to a locally unique value in the operational
        state.";
    }
    leaf description {
      type string;
      description "a textual description of inventory object";
    }
    leaf alias {
      type string;
      description 
      "a alias name of inventory objects. This alias name can be 
      specified by network manager.";
    }
  }
 
  grouping ne-specific-info-grouping {
    description
      "Attributes applicable to network elements.";
    leaf hardware-rev {
      config false;
      type string;
      description
        "The vendor-specific hardware revision string for the NE.";
    }
    leaf software-rev {
      config false;
      type string;
      description
        "The vendor-specific software revision string for the NE.";
    }
    leaf mfg-name {
      config false;
      type string;
      description "The name of the manufacturer of this NE";
    }
    leaf mfg-date {
      config false;
      type yang:date-and-time;
      description "The date of manufacturing of the NE.";
    }
    leaf serial-number {
      config false;
      type string;
      description
        "The vendor-specific serial number of NE. It is expected that
        vendors assign unique serial numbers to different NEs within 
        the scope of the part number.";
    }
    leaf product-name {
      config false;
      type string;
      description
        "The vendor-specific and human-interpretable string describing
		the network element type. It is expected that vendors assign 
		unique product names to different NE types within the scope of
		the vendor.";
    }
  }

 grouping pon-ne-specific-info-grouping {
    description
      "Attributes applicable to pon network elements.";
   leaf ne-class{
      config false;
      type string;
      description
        "Type of an NE.Value range: OLT/ONU .";
    }
    leaf communication-status{
      config false;
      type string;
      description
        "Communication status of an NE. Value range: normal/interrupt/unkonw";
    }
	leaf admin-status {
      config false;
      type string;
      description
        "Management status of an NE. Value range: active/inactive/test/maintenance/unkonw";
    }
	leaf create-date-and-time {
      config false;
      type string;
      description
        "NE creation time, in UTC or local format. The default format is UTC.";
    }
    leaf last-modified-date-and-time {
      config false;
      type string;
      description
        "NE modification time, in UTC or local format. The default format is UTC.";
    }
    leaf ipv4-address {
      config false;
      type string;
      description
        "IPv4 address of an NE.";
    }
    leaf ipv6-address {
      config false;
      type string;
      description
        "IPv6 address of an NE.";
    }
    leaf mac {
      config false;
      type string;
      description
        "MAC address corresponding to the management IP address.";
    }
}

 grouping onu-specific-info-grouping {
    description
      "Attributes applicable to onu network elements.";
    leaf ref-parent-ne {
      config false;
      type string;
      description
        "ID of the parent NE to which an NE belongs. The type is UUID.";
    } 
   leaf ref-parent-tp{
      config false;
      type string;
      description
        "Indicates the ID of the PON port to which the ONU is connected. The type is UUID.";
    }
	leaf onu-class {
      config false;
      type string;
      description
        "Indicates the ONU type. Value range: MDU/ONT.";
    }
	leaf onu-id {
      config false;
      type int32;
      description
        "ONU ID.";
    }
    leaf pon-type {
      config false;
      type string;
      description
        "Indicates the PON type. Value range: GPON/EPON/XG-PON/XGS-PON/XG_G-PON/XGS-G-PON/Flex-PON/10G-EPON.";
    }
   leaf loid {
      config false;
      type string;
      description
        "Indicates the ONU authentication information.";
    }
    leaf last-down-time {
      config false;
      type string;
      description
        "Indicates the last time when an ONU goes offline. The time is the local time of the system.";
    }
}
  
  grouping component-specific-info-grouping {
    description 
      "Provide component-specific attributes for different 
      components.";
	
    container chassis-specific-info {
	  when "../class = 'ianahw:chassis'";
	  description 
        "This container contains some attributes belong to
        chassis only.";
	  uses chassis-specific-info-grouping;
	  config false;
	}
	
	container slot-specific-info {
	  when "../class = 'ianahw:container'";
	  description 
        "This container contains some attributes belong to
        slot only.";
	  uses slot-specific-info-grouping;
	  config false;
	}
	
	container board-specific-info {
	  when "../class = 'ianahw:module'";
	  description 
        "This container contains some attributes belong to
        board only.";
	  uses board-specific-info-grouping;
	  config false;
	}
	
	container port-specific-info {
	  when "../class = 'ianahw:port'";
	  description 
        "This container contains some attributes belong to
        port only.";
	  uses port-specific-info-grouping;
	  config false;
	}
	
	container software-specific-info {
	  when "../class = 'ianahw:software'";
	  description 
        "This container contains some attributes belong to
        software only.";
	  uses software-specific-info-grouping;
	  config false;
	}
  }

  grouping chassis-specific-info-grouping {
  //To be enriched in the future.
    description
      "Specific attributes applicable to chassis only.";
  }
  
  grouping slot-specific-info-grouping {
  //To be enriched in the future.
    description
      "Specific attributes applicable to slots only.";
  }
  
  grouping board-specific-info-grouping {
  //To be enriched in the future.
    description
      "Specific attributes applicable to boards only.";
  }
  
  grouping port-specific-info-grouping {
  //To be enriched in the future.
    description
      "Specific attributes applicable to ports only.";
  }

  grouping software-specific-info-grouping {
  //To be enriched in the future.
    description
      "Specific attributes applicable to software only.";
  }  
  
  grouping ne-info-grouping {  
    container network-elements {
      description
        "The top-level container for the list of network elements 
        within the network.";
      list network-element {
        key ne-id;
        description
          "The list of network elements within the network.";
        leaf ne-id {
          type string;
          description
            "Network Element (NE) identifier.";
        }
        leaf ne-type {
          config false;
          type identityref {
            base ne-type;
          }
          default "ne-physical";
          description
            "The type of network element (NE).";
        }
        uses common-entity-attributes;
        uses ne-specific-info-grouping;
        uses pon-ne-specific-info-grouping;
        uses onu-specific-info-grouping;
        container components {
          description
            "The top-level container for the list of components 
            within a network element.";
          list component {
            key component-id;
            description
              "The list of components within a network element.";
            leaf component-id {
              type string;
              description
                "Component identifier";
            }
          leaf class {
            config false;
            type union {
              type identityref {
                base ianahw:hardware-class;
              }
              type identityref {
                base non-hardware-component-class;
              }
            }
            mandatory true;
            description
              "The type of the component.";
          }
  
            uses common-entity-attributes;
            container child-component-ref {
              config false;
              description
                "A placeholder for adding the reference to child 
                component(s): to further discuss whether to define 
                a child leaf-list as RFC8348 or a list of 
                sub-components as openconfig-platform.";
            }
            leaf parent-rel-pos {
              config false;
              type int32 {
                range "0 .. 2147483647";
              }
              description
                "The relative position with respect to the parent
                component among all the sibling components.";
              reference
                "RFC 6933: Entity MIB (Version 4) -
                          entPhysicalParentRelPos";
            }
            container parent-component-ref {
              config false;
              description
                "A placeholder for adding the reference to parent 
                component(s): to further discuss whether to define 
                a parent attribute as RFC8348 or a 
                parent-component-references container as in 
                draft-ietf-ccamp-network-inventory-yang-02.";
            }
            leaf hardware-rev {
              config false;
              type string;
              description
                "The vendor-specific hardware revision string for the
                component.  The preferred value is the hardware 
                revision identifier actually printed on the component 
                itself (if present).";
              reference
                "RFC 6933: Entity MIB (Version 4) -
                          entPhysicalHardwareRev";
            }
            leaf firmware-rev {
              config false;
              type string;
              description
                "The vendor-specific firmware revision string for the
                component.";
              reference
                "RFC 6933: Entity MIB (Version 4) -
                          entPhysicalFirmwareRev";
            }
            leaf software-rev {
              config false;
              type string;
              description
                "The vendor-specific software revision string for the
                component.";
              reference
                "RFC 6933: Entity MIB (Version 4) -
                          entPhysicalSoftwareRev";
            }           
            leaf serial-num {
              config false;
              type string;
              description
                "The vendor-specific serial number of the component 
                instance. It is expected that vendors assign unique 
                serial numbers to different component instances within
                the scope of the part number.";
            }
            leaf mfg-name {
              config false;
              type string;
              description
                "The name of the manufacturer of this physical 
                component.
                The preferred value is the manufacturer name string
                actually printed on the component itself (if present).
  
                Note that comparisons between instances of the
                'model-name', 'firmware-rev', 'software-rev', and
                'serial-num' nodes are only meaningful amongst 
                components with the same value of 'mfg-name'.
  
                If the manufacturer name string associated with the
                physical component is unknown to the server, then this
                node is not instantiated.";
              reference
                "RFC 6933: Entity MIB (Version 4) - 
                entPhysicalMfgName";
            }
            leaf part-number {
              config false;
              type string;
              description
                "The vendor-specific part number of the component 
                type. It is expected that vendors assign unique part
                numbers to different component types within the scope
                of the vendor.";
            }
            leaf product-name {
              config false;
              type string;
              description
                "The vendor-specific and human-interpretable string 
                describing the component type. It is expected that 
                vendors assign unique product names to different 
                component types within the scope of the vendor.";
            } 
            leaf asset-id {
              config false;
              type string;
              description
                "This node is a user-assigned asset tracking 
                identifier for the component.
  
                A server implementation MAY map this leaf to the
                entPhysicalAssetID MIB object.  Such an implementation
                needs to use some mechanism to handle the differences 
                in size and characters allowed between this leaf and
                entPhysicalAssetID.  The definition of such a 
                mechanism is outside the scope of this document.";
              reference
                "RFC 6933: Entity MIB (Version 4) - 
                entPhysicalAssetID";
            }
            leaf is-fru {
              config false;
              type boolean;
              description
                "This node indicates whether or not this component is
                considered a 'field-replaceable unit' by the vendor.  
                If this node contains the value 'true', then this 
                component identifies a field-replaceable unit.  
                For all components that are permanently contained 
                within a field-replaceable unit, the value 'false' 
                should be returned for this node.";
              reference
                "RFC 6933: Entity MIB (Version 4) - entPhysicalIsFRU";
            }
            leaf mfg-date {
              config false;
              type yang:date-and-time;
              description
                "The date of manufacturing of the managed component.";
              reference
                "RFC 6933: Entity MIB (Version 4) - 
                entPhysicalMfgDate";
            }
            leaf-list uri {
              config false;
              type inet:uri;
              description
                "This node contains identification information about 
                the component.";
              reference
                "RFC 6933: Entity MIB (Version 4) - entPhysicalUris";
            }
            
            uses component-specific-info-grouping;
          }
        }
      }
    }
  }
  
  container network-inventory {
    uses ne-info-grouping;
    
  }
}
